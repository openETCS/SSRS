# Specification: Specification Document
- Description: Functional Blocks

## R2 (Function Block Type)
Movement authority
- Variable Link Type -> R3
- Variable Link Type -> R7
- links to -> 3.6.1.1

### REQ-1 (Requirement Type)
Requirement One

### REQ-2 (Requirement Type)
Requirement Two

# Specification
- Description: Variables

## R3: test_variable1 (Variable Type)

### R4: var_component1 (Variable Type)

### R5: var_component2 (Variable Type)

### R6: var_component3 (Variable Type)

## R7: test_variable2 (Variable Type)

# Specification
- Description: SRS Items

## 3.6.1.1 (SRS Item)
Optionally some text

## 3.4.4.2.1 (SRS Item)
Some more text
